module sonic-2-lists {

    yang-version 1.1;

	namespace "http://github.com/Azure/s-2-lists";
	prefix s-2-lists;

	container sonic-2-lists {
		/* sonic-2-lists - top level container */

		container TABLE_1 {
			/* TALBE_1 - table container */


			description "TABLE_1 description";

			list TABLE_1_LIST_1 {
				/* TALBE_1_LIST_1 - object container */

				description "TABLE_1_LIST_1 description";

				key "key_name1";

				leaf key_name1 {
					type string;
				}
			}

			list TABLE_1_LIST_2 {
				/* TALBE_1_LIST_2 - object container */

				description "TABLE_1_LIST_2 description";

				key "key_name2";

				leaf key_name2 {
					type string;
				}
			}
		}
	}
}
