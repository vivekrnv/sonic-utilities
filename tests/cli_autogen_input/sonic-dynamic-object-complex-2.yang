module sonic-dynamic-object-complex-2 {

    yang-version 1.1;

	namespace "http://github.com/Azure/dynamic-complex-2";
	prefix dynamic-complex-2;

	container sonic-dynamic-object-complex-2 {
		/* sonic-dynamic-object-complex-2 - top level container */

		container TABLE_1 {
			/* TABLE_1 - table container */

			description "TABLE_1 description";

			list OBJECT_1_LIST {
				/* OBJECT_1_LIST - dynamic object container, it have:
				 * 2 keys
				 * 2 leaf,
				 * 2 leaf-list
				 * 2 choice
				 */

				description "OBJECT_1_LIST description";

				key "KEY_LEAF_1 KEY_LEAF_2";

				leaf KEY_LEAF_1 {
					description "KEY_LEAF_1 description";
					type string;
				}

				leaf KEY_LEAF_2 {
					description "KEY_LEAF_2 description";
					type string;
				}

				leaf OBJ_1_LEAF_1 {
					description "OBJ_1_LEAF_1 description";
					type string;
				}

				leaf OBJ_1_LEAF_2 {
					description "OBJ_1_LEAF_2 description";
					type string;
				}

				leaf-list OBJ_1_LEAF_LIST_1 {
					type string;
				}

				leaf-list OBJ_1_LEAF_LIST_2 {
					type string;
				}

				choice OBJ_1_CHOICE_1 {
					case OBJ_1_CHOICE_1_CASE_1 {
						leaf OBJ_1_CHOICE_1_LEAF_1 {
							type uint16;
						}
					}
					case OBJ_1_CHOICE_1_CASE_2 {
						leaf OBJ_1_CHOICE_1_LEAF_2 {
							type string;
						}
					}
				}

				choice OBJ_1_CHOICE_2 {
					case OBJ_1_CHOICE_2_CASE_1 {
						leaf OBJ_1_CHOICE_2_LEAF_1 {
							type uint16;
						}
					}
					case OBJ_1_CHOICE_2_CASE_2 {
						leaf OBJ_1_CHOICE_2_LEAF_2 {
							type string;
						}
					}
				}
			}
		}
	}
}
